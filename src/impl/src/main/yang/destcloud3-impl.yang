module destcloud3-impl {
    yang-version 1;
    namespace "urn:opendaylight:params:xml:ns:yang:destcloud3:impl";
    prefix "destcloud3-impl";

    import config { prefix config; revision-date 2013-04-05; }
    import opendaylight-md-sal-binding { prefix md-sal-binding; revision-date 2013-10-28;}

    description
        "Service definition for destcloud3 project";

    revision "2014-12-10" {
        description
            "Initial revision";
    }

    identity destcloud3 {
        base config:module-type;
        config:java-name-prefix Destcloud3;
    }

    augment "/config:modules/config:module/config:configuration" {
        case destcloud3 {
            when "/config:modules/config:module/config:type = 'destcloud3'";
            container broker {
                uses config:service-ref {
                    refine type {
                        mandatory true;
                        config:required-identity md-sal-binding:binding-broker-osgi-registry;
                    }
                }
            }
        }
    }
}
